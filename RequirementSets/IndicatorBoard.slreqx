# IndicatorBoard
This is the requirement set for the Indicator Board used for the 2024 EcoCar challenge.

## IB1.1: Propulstion System Status LED On; this should illuminate whenever full torque is available. I.e., when any drive mode is enabled. (Functional)
Name: Propulstion System Status LED
LED ON: LED should turn on when the system is enabled and there are no faults. The Indicator Board should be active as well.

## IB2.1: HV System Status LED On; this should illuminate when the energy storage system contactors are closed and energy storage system is able to provide current to a drive system, without fault, or facilitate on-plug charging. (Functional)
Name: HV System Status LED
LED ON: LED should be on when the battery contactors are closed, there are no isolation faults, one of the drive modes are enabled, and the Indicator Board is enabled.

## IB3.1: CAV Longitudinal Control Status On; this should illuminate when the longitudinal CAV system is connected and able to communicate with the CSC - must be illuminated to initialize any longitudinal CAV feature. (Functional)
Name: CAV Longitudinal Control Status
LED ON: LED should be on when there is 12V supplied to the AUTERA device, the longitudinal CAV system is switched on, the CAV system status light is on, and the Indicator Board is active.

## IB4.1: CAV Lateral Control Status On; this should illuminate when the lateral CAV system is connected and able to communicate with the CSC - must be illuminated to initialize any lateral CAV feature. (Functional)
Name: CAV Lateral Control Status
LED ON: LED should be on when there is 12V supplied to the AUTERA device, the latitudinal CAV system is switched on, the CAV system status light is on, and the Indicator Board is active.

## IB5.1: CAV V2X Status On; this should illuminate when use of V2X information for CAV features is allowable. (Functional)
Name: CAV V2X Status
LED ON: LED should be on when there is 12V supplied to the AUTERA device, the CAV V2X system is switched on, the CAV system status light is on, and the Indicator Board is active.

## IB1.2: Propulstion System Status LED Flashing; when faults are present that prevents the use of the propulsions system. (Functional)
Name: Propulstion System Status LED
LED Flashing: LED must be flashing when either the Propulsion System faults or the Electronic Drive Unit faults are present that prevents the use of the propulsions system.

## IB1.3: Propulstion System Status LED Off; when the vehicle is unable to respond to control inputs. (Functional)
Name: Propulstion System Status LED
LED OFF: LED should turn off when the system and Indicator Board are disabled.

## IB2.2: HV System Status LED Flashing; Ground Fault Indicator: Illuminated within 60s of when the vehicle ground fault monitor detects a ground fault. (Functional)
Name: HV System Status LED
LED Flashing: LED should be flashing when there is an isolation fault within 60s of the rising edge of the fault triggering.

## IB2.3: HV System Status LED Off; when Energy storage system Contactors are open (Functional)
Name: HV System Status LED
LED OFF: When battyer contactors are open and the Indicator Board is active.

## IB3.2: CAV Longitudinal Control Status Flashing; when faults are present that prevents the use of any longitudinal control feature. (Functional)
Name: CAV Longitudinal Control Status
LED Flashing: LED should be flashing when there is 12V supplied to the AUTERA device, the longitudinal CAV system is switched on, the CAV system status light is flashing, and the Indicator Board is active.

## IB3.3: CAV Longitudinal Control Status Off; when the “CAV Longitudinal Control” switch is in the off position. (Functional)
Name: CAV Longitudinal Control Status
LED OFF: LED should be off when there is no voltage supplied to the AUTERA device, the longitudinal CAV system is switched off, the CAV system status light is off, and the Indicator Board is active.

## IB4.2: CAV Lateral Control Status Flashing; when faults are present that prevents the use of any lateral control feature. (Functional)
Name: CAV Lateral Control Status
LED Flashing: LED should be flashing when there is 12V supplied to the AUTERA device, the latitudinal CAV system is switched on, the CAV system status light is flashing, and the Indicator Board is active.

## IB4.3: CAV Lateral Control Status Off; when the “CAV Lateral Control” switch is in the off position. (Functional)
Name: CAV Lateral Control Status
LED OFF: LED should be off when there is no voltage supplied to the AUTERA device, the latitudinal CAV system is switched off, the CAV system status light is off, and the Indicator Board is active.

## IB5.2: CAV V2X Status Flashing; when faults are present that prevent the use of any V2X data retrieval e.g., disconnected C-V2X radio. (Functional)
Name: CAV V2X Status
LED Flashing: LED should be flashing when there is 12V supplied to the AUTERA device, the CAV V2X system is switched on, the CAV system status light is flashing, and the Indicator Board is active.

## IB5.3: CAV V2X Status Off; when the “CAV V2X Control” switch is in the off position. (Functional)
Name: CAV V2X Status
LED OFF: LED should be off when there is no voltage supplied to the AUTERA device, the CAV V2X system is switched off, the CAV system status light is off, and the Indicator Board is active.
