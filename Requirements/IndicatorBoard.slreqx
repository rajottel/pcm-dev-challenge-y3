# IndicatorBoard
This is the requirement set for the Indicator Board used for the 2024 EcoCar challenge.

## IB1: Propulstion System Status LED; this should illuminate whenever full torque is available. I.e., when any drive mode is enabled. (Functional)
Name: Propulstion System Status LED
LED ON: When any drive mode is enabled and will respond to control inputs - full torque available.
LED Flashing: When faults are present that prevents the use of the propulsions system.
LED OFF: When the vehicle is unable to respond to control inputs.

## IB2: HV System Status LED; this should illuminate when the energy storage system contactors are closed and energy storage system is able to provide current to a drive system, without fault, or facilitate on-plug charging. (Functional)
Name: HV System Status LED
LED ON: When the Energy storage system contactors are closed and Energy storage system is able to provide current to a drive system, without fault, or facilitate on-plug charging. (This includes off and charging conditions)
LED Flashing: Ground Fault Indicator: Illuminated within 60s of when the vehicle ground fault monitor detects a ground fault.
LED OFF: When Energy storage system Contactors are open

## IB3: CAV Longitudinal Control Status; this should illuminate when the longitudinal CAV system is connected and able to communicate with the CSC - must be illuminated to initialize any longitudinal CAV feature. (Functional)
Name: CAV Longitudinal Control Status
LED ON: When the longitudinal CAV system is physically connected to and able to communicate with the CSC, i.e. (Long. control system is enabled and ready to provide commands.). Must be illuminated to initialize any CAV feature.
LED Flashing: When faults are present that prevents the use of any longitudinal control feature.
LED OFF: When the “CAV Longitudinal Control” switch is in the off position.

## IB4: CAV Lateral Control Status; this should illuminate when the lateral CAV system is connected and able to communicate with the CSC - must be illuminated to initialize any lateral CAV feature. (Functional)
Name: CAV Lateral Control Status
LED ON: When the lateral CAV system is physically connected to and able to communicate with the CSC, i.e. (Lat. control system is enabled and ready to provide the features.). Must be illuminated to initialize any lateral control features.
LED Flashing: When faults are present that prevents the use of any lateral control feature.
LED OFF: When the “CAV Lateral Control” switch is in the off position.

## IB5: CAV V2X Status; this should illuminate when use of V2X information for CAV features is allowable. (Functional)
Name: CAV V2X Status
LED ON: When use of V2X information for CAV features is allowable.
LED Flashing: When faults are present that prevent the use of any V2X data retrieval e.g., disconnected C-V2X radio.
LED OFF: When the “CAV V2X Control” switch is in the off position.
