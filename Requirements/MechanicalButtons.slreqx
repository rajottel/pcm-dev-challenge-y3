# MechanicalButtons

## MB1: Regenerative Braking; this switch controls the enablement of regenerative braking. Disabling this switch causes the car to solely rely on hydraulic brakes. (Functional)
Name: Regenerative Braking
Purpose: This switch controls the enablement of regenerative braking. Disabling this switch causes the car to solely rely on hydraulic brakes. It is used during On-Road Safety Evaluations to disable regenerative braking to ensure the vehicle is able stop solely on hydraulic friction brakes.
Engaged/ON: The vehicle is able to utilize regenerative braking as a part of the normal vehicle control strategy.
Disengaged/OFF: The vehicle shall never use traction motors to apply negative torque during braking maneuvers.

## MB2: CAV Longitudinal Control; this siwtch allows automated longitudinal control commands to be sent by CAV Supervisory Controller(s). (Functional)
Name: CAV Longitudinal Control
Purpose: This switch will allow automated longitudinal control commands to be sent by CAV Supervisory Controller(s), enabling operators to initiate automated longitudinal control features. Once the switch is turned on, operators will still need to initiate features using other buttons in the vehicle.
Engaged/ON: The vehicle longitudinal control features are allowed and may be initiated by operator.
Disengaged/OFF: The vehicle shall operate as if it has no longitudinal control features. Like, CAV Supervisory Controller(s) shall not send messages to propulsion system controller that would request longitudinal control actions; Propulsion Supervisory Controller shall not send any automated torque requests to propulsion system components, nor shall it use any CAV Supervisory Controller(s) data to adjust propulsion system commands; Perception and connectivity systems shall still operate and report detections, if engaged.

## MB3: CAV Lateral Control; this switch allows automated lateral control commands to be sent by the CAV Supervisory Controller(s). (Functional)
Name: CAV Lateral Control
Purpose: This switch will allow automated lateral control commands to be sent by the CAV Supervisory Controller(s), enabling operators to initiate automated lateral control features. Once the switch is turned to on, operators will still need to initiate features using other buttons in the vehicle.
Engaged/ON: Vehicle lateral control features are allowed and may be initiated by operator.
Disengaged/OFF: Vehicle shall operate as if it has no lateral control features. Like, Propulsion Supervisory Controller shall not send any automated torque requests to propulsion system components, nor shall it use any CAV Supervisory Controller(s) data to adjust propulsion system commands.

## MB4: CAV V2X Control; this switch will allow the use of V2X information for CAV features when available. (Functional)
Name: CAV V2X Control
Purpose: This switch will allow the use of V2X information for CAV features when available. This switch should have no effect when longitudinal control switch is turned off.
Engaged/ON: Vehicle CAV features requiring V2X are allowed and may be initiated by operator.
Disengaged/OFF: Vehicle shall be able to engage longitudinal and lateral control without V2X features if permitted per control switches. Propulsion Supervisory Controller shall not use any V2X data or control requests coming from the CAV Supervisory Controller(s) - Perception system shall still operate and report data.
