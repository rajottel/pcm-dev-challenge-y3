# IndicatorBoard
This is the requirement set for the Indicator Board used for the 2024 EcoCar challenge.

## IB1: Propulstion System Status LED; this should illuminate whenever full torque is available. I.e., when any drive mode is enabled. (Functional)
Propulstion System Status LED; this should illuminate whenever full torque is available. I.e., when any drive mode is enabled. If flashing, something is preventing the drive mode from enabling. If not illuminated, the vehicle is unable to respond to any control inputs.

## IB2: HV System Status LED; this should illuminate when the energy storage system contactors are closed and energy storage system is able to provide current to a drive system, without fault, or facilitate on-plug charging. (Functional)
HV System Status LED; this should illuminate when the energy storage system contactors are closed and energy storage system is able to provide current to a drive system, without fault, or facilitate on-plug charging. If flashing, the ground fault monitor detects a ground fault. If not illuminated, Eneergy storage system contactors are open.

## IB3: CAV Longitudinal Control Status; this should illuminate when the longitudinal CAV system is connected and able to communicate with the CSC - must be illuminated to initialize any longitudinal CAV feature. (Functional)
CAV Longitudinal Control Status; this should illuminate when the longitudinal CAV system is connected and able to communicate with the CSC - must be illuminated to initialize any CAV feature. If flashing, faults are preventing the use of any longitudinal control feature. If not illuminated, "CAV Longitudinal Control" switch is in the off position.

## IB4: CAV Lateral Control Status; this should illuminate when the lateral CAV system is connected and able to communicate with the CSC - must be illuminated to initialize any lateral CAV feature. (Functional)
CAV Lateral Control Status; this should illuminate when the lateral CAV system is connected and able to communicate with the CSC - must be illuminated to initialize any lateral CAV feature. If flashing, faults are preventing the use of any lateral control feature. If not illuminated, "CAV Lateral Control" switch is in the off position.

## IB5: CAV V2X Status; this should illuminate when use of V2X information for CAV features is allowable. (Functional)
CAV V2X Status; this should illuminate when use of V2X information for CAV features is allowable. If flashing, faults are present that prevent the use of any V2X data retrieval. If not illuminated, “CAV V2X Control” switch is in the off position.
