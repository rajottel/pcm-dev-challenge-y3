# DevChallangeRequirments

## #1: If a simultanious input is detected, EDU fault is present or an Accelerator fault is present, the arbitrated pedal position must be 0 (Functional)

## #2: If no simultanious input is detected and no fault is present form the EDU or Accelerator pedal, the arbitrated pedal position must be equal to the accelerator pedal position (Functional)

## #3: Effective Pedal Position AND Actual Pedal Position must always equal arbitrated accelerator position (Functional)

## #4: 0 torque should be commended if the accelerator pedal is pressed AND the vehicle is in neutral. (Functional)

## #5: 0 torque should be commended if the accelerator pedal is pressed AND the vehicle is in park. (Functional)

## #6: When in drive, torque command must be positive (Functional)

## #7: When In reverse, torque command must be negative (Functional)

## #8: Disagreement fault must have a value of 1 if the accelerator pedal position primary and accelerator pedal position secondary differ (Functional)

## #9: The primary out of range fault must have a value of 1 if the primary pedal position is outside the range 0-100 (Functional)

## #10: The secondary out of range fault must have a value of 1 if the secondary pedal position is outside the range 0-100 (Functional)

## #11: The Accelerator pedal fault must have a value of 1 if a disagreement fault, primary OOR or secondary OOR fault occur. (Functional)
